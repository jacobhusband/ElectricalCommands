(defun c:TSELECT ( / ss ssNew i ent objType)
  (prompt "\nSelect objects: ")
  (setq ss (ssget))
  (if ss
    (progn
      (setq ssNew (ssadd))
      (setq i 0)
      (while (< i (sslength ss))
        (setq ent (ssname ss i))
        (setq objType (cdr (assoc 0 (entget ent))))
        (if (or (= objType "TEXT") (= objType "MTEXT"))
          (setq ssNew (ssadd ent ssNew))
        )
        (setq i (1+ i))
      )
      (if (> (sslength ssNew) 0)
        (progn
          (sssetfirst nil ssNew)
          (prompt (strcat "\nSelected " (itoa (sslength ssNew)) " text objects."))
        )
        (prompt "\nNo TEXT or MTEXT objects found in selection.")
      )
    )
    (prompt "\nNothing selected.")
  )
  (princ)
)
